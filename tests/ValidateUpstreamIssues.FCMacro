# SPDX-License-Identifier: LGPL-2.1-or-later
"""Quick issue regressions against the existing fork; does not build/install code.

Set FREECAD_PLUS_SOURCE and FREECAD_PLUS_VALIDATION_DIR; use isolated preferences.
Mirror tests load from source so an old binary can demonstrate the regression.
"""
import hashlib
import importlib.util
import json
import os
import sys
from pathlib import Path
import traceback
import unittest

import FreeCAD as App
import FreeCADGui as Gui
from PySide import QtCore, QtWidgets

output = Path(os.environ["FREECAD_PLUS_VALIDATION_DIR"])
output.mkdir(parents=True, exist_ok=True)
source = Path(os.environ["FREECAD_PLUS_SOURCE"])
report = {"version": App.Version(), "application": App.ConfigGet("AppHomePath"), "suites": []}
window = Gui.getMainWindow()
window.setAttribute(QtCore.Qt.WA_DontShowOnScreen, True)
window.show()
Gui.updateGui()
attributes = window.findChild(QtWidgets.QDockWidget, "Model")
if attributes:
    trees = [widget for widget in attributes.findChildren(QtWidgets.QWidget)
             if widget.metaObject().className().endswith("TreePanel")]
    report["native_attributes"] = {"title": attributes.windowTitle(),
        "tree_hidden": bool(trees) and all(widget.isHidden() for widget in trees)}
try:
    paths = [source / name for name in os.environ.get("FREECAD_PLUS_ISSUE_TESTS",
        "src/Mod/Part/parttests/TestPartMirror.py,src/Mod/CAM/CAMTests/TestPathOpUtil.py,"
        "tests/TestIssueQuantityInput.py,tests/TestIssueTreeSelection.py,"
        "src/Mod/PartDesign/PartDesignTests/TestExtrudeTaskPanel.py,tests/TestIssueMirrorGui.py,"
        "tests/TestIssueSurfaceAvoidance.py,tests/TestIssueLineCoverage.py,tests/TestIssueFreeformBoundary.py"
    ).split(",")]
    for path in paths:
        # Selected test modules may share sibling fixtures; this adds test paths,
        # not application source overlays, to the isolated native harness.
        if str(path.parent) not in sys.path:
            sys.path.insert(0, str(path.parent))
        spec = importlib.util.spec_from_file_location(path.stem, path)
        module = importlib.util.module_from_spec(spec)
        spec.loader.exec_module(module)
        with (output / (path.stem + ".log")).open("w", encoding="utf-8", buffering=1) as stream:
            names = os.environ.get("FREECAD_PLUS_TEST_NAMES", "")
            suite = (unittest.defaultTestLoader.loadTestsFromNames(names.split(","), module)
                     if names else unittest.defaultTestLoader.loadTestsFromModule(module))
            result = unittest.TextTestRunner(stream=stream, verbosity=2).run(suite)
        report["suites"].append({
            "name": path.stem, "source": str(path),
            "test_filter": names,
            "sha256": hashlib.sha256(path.read_bytes()).hexdigest(),
            "run": result.testsRun, "passed": result.wasSuccessful(),
            "failures": [(str(t), msg) for t, msg in result.failures],
            "errors": [(str(t), msg) for t, msg in result.errors],
            "skipped": [(str(t), msg) for t, msg in result.skipped],
        })
    report["passed"] = all(s["passed"] and not s["skipped"] for s in report["suites"])
except BaseException:
    report["passed"] = False
    report["harness_error"] = traceback.format_exc()
finally:
    report["source_overlay"] = os.environ.get("FREECAD_PLUS_PROFILE_SOURCE") == "1"
    report["runtime_modules"] = {}
    for name in ("ComponentModel", "ComponentSketch", "ComponentExtrude", "ComponentRevolve", "ComponentLoft", "ComponentPipe", "ComponentHelix", "ComponentPrimitive", "ComponentNativeOperation", "ComponentProfile",
                 "ComponentExtent", "ComponentResultView", "freecad.gui.ComponentNavigator",
                 "freecad.gui.ComponentExtrudeTask", "freecad.gui.ComponentRevolveTask", "freecad.gui.ComponentLoftTask",
                 "freecad.gui.ComponentOperationTask", "freecad.gui.ComponentSectionTask",
                 "freecad.gui.ComponentPipeTask", "freecad.gui.ComponentHelixTask", "freecad.gui.ComponentPrimitiveTask", "freecad.gui.ComponentSketchTask",
                 "freecad.gui.ComponentSelection", "freecad.gui.OccurrenceMove", "freecad.gui.PlusRibbon"):
        module = sys.modules.get(name)
        filename = getattr(module, "__file__", "")
        if filename:
            path = Path(filename)
            expected = source / ("src/Gui" if name.startswith("freecad.gui.") else "src/Mod/Part") / (name.rsplit(".", 1)[-1] + ".py")
            digest = hashlib.sha256(path.read_bytes()).hexdigest() if path.is_file() else None
            report["runtime_modules"][name] = {"path": filename,
                "sha256": digest,
                "matches_source": expected.is_file() and digest == hashlib.sha256(expected.read_bytes()).hexdigest(),
                "in_build": path.resolve().is_relative_to(Path(App.ConfigGet("AppHomePath")).resolve())}
    if os.environ.get("FREECAD_PLUS_VERIFY_PAYLOAD") == "1":
        required = {"ComponentModel", "ComponentSketch", "ComponentExtrude", "ComponentProfile",
                    "ComponentExtent", "ComponentResultView", "freecad.gui.ComponentNavigator",
                    "freecad.gui.ComponentExtrudeTask", "freecad.gui.ComponentSketchTask",
                    "freecad.gui.ComponentSelection", "freecad.gui.OccurrenceMove"}
        report["payload_verified"] = (required.issubset(report["runtime_modules"]) and not report["source_overlay"]
            and all(entry["matches_source"] and entry["in_build"] for entry in report["runtime_modules"].values()))
        report["passed"] = (report["passed"] and report["payload_verified"]
            and report.get("native_attributes") == {"title": "Attributes", "tree_hidden": True})
    report["tests_run"] = sum(s["run"] for s in report["suites"])
    (output / "results.json").write_text(json.dumps(report, indent=2), encoding="utf-8")
    (output / "validation.done").write_text("PASS" if report["passed"] else "FAIL")
    for doc in list(App.listDocuments().values()):
        App.closeDocument(doc.Name)
    QtCore.QTimer.singleShot(100, QtWidgets.QApplication.instance().quit)
