# SPDX-License-Identifier: LGPL-2.1-or-later
"""Run CAM tests in the source-built GUI; see CAMMeshMachining.md."""

import hashlib
import importlib
import json
import os
from pathlib import Path
import traceback
import unittest

import FreeCAD as App
import FreeCADGui as Gui
from PySide import QtCore, QtWidgets

output = Path(os.environ["FREECAD_PLUS_VALIDATION_DIR"])
output.mkdir(parents=True, exist_ok=True)
report = {"version": App.Version(), "application": App.ConfigGet("AppHomePath"), "suites": []}
window = Gui.getMainWindow()
window.setAttribute(QtCore.Qt.WA_DontShowOnScreen, True)
window.show()
Gui.updateGui()
try:
    modules = os.environ.get("FREECAD_PLUS_CAM_TESTS", "TestMeshMachining").split(",")
    for name in modules:
        module = importlib.import_module("CAMTests." + name)
        with (output / (name + ".log")).open("w", encoding="utf-8", buffering=1) as stream:
            result = unittest.TextTestRunner(stream=stream, verbosity=2).run(
                unittest.defaultTestLoader.loadTestsFromModule(module))
        report["suites"].append({
            "name": name, "module": module.__file__,
            "sha256": hashlib.sha256(Path(module.__file__).read_bytes()).hexdigest(),
            "run": result.testsRun, "passed": result.wasSuccessful(),
            "failures": [(str(t), msg) for t, msg in result.failures],
            "errors": [(str(t), msg) for t, msg in result.errors],
            "skipped": [(str(t), msg) for t, msg in result.skipped],
        })
        (output / "results.json").write_text(json.dumps(report, indent=2), encoding="utf-8")
    report["passed"] = all(s["passed"] and not s["skipped"] for s in report["suites"])
except BaseException:
    report["passed"] = False
    report["harness_error"] = traceback.format_exc()
finally:
    report["tests_run"] = sum(s["run"] for s in report["suites"])
    (output / "results.json").write_text(json.dumps(report, indent=2), encoding="utf-8")
    (output / "validation.done").write_text("PASS" if report["passed"] else "FAIL")
    for doc in list(App.listDocuments().values()):
        App.closeDocument(doc.Name)
    QtCore.QTimer.singleShot(100, QtWidgets.QApplication.instance().quit)
